RADIXWARE-MIB DEFINITIONS ::= BEGIN

IMPORTS
        OBJECT-TYPE
                FROM RFC-1212
        TEXTUAL-CONVENTION,
        DisplayString,
        DateAndTime
                FROM SNMPv2-TC
        MODULE-IDENTITY,
        NOTIFICATION-TYPE,
        Integer32,
        enterprises
                FROM SNMPv2-SMI
        OBJECT-GROUP,
        MODULE-COMPLIANCE,
        NOTIFICATION-GROUP
                FROM SNMPv2-CONF
        ;

radixware MODULE-IDENTITY
        LAST-UPDATED "201312301200Z"
        ORGANIZATION
                "Compass Plus"
        CONTACT-INFO
                "Compass Plus, Ltd
                Lenina 68 
                Magnitogorsk
                Russia

                Internet: http://www.compassplus.com/
                E-mail:
                "
        DESCRIPTION
                "Template for MIB file generated by systems based on 
                Radixware Platform
                "
        REVISION "201312301800Z"
        DESCRIPTION
                "Initial revision"
        ::= {cplus 1}

cplus   OBJECT IDENTIFIER ::= {enterprises 43238}

snmpSystemId    OBJECT IDENTIFIER ::= {radixware ${snmpSystemId}}

admin                       OBJECT IDENTIFIER ::= {snmpSystemId 1}

snmpObjectGroups            OBJECT IDENTIFIER ::= {admin 1}
snmpNotificationGroups      OBJECT IDENTIFIER ::= {admin 2}
mibCompliances              OBJECT IDENTIFIER ::= {admin 3}

metrics                     OBJECT IDENTIFIER ::= {snmpSystemId 2}

notifications               OBJECT IDENTIFIER ::= {snmpSystemId 3}
notificationTypes           OBJECT IDENTIFIER ::= {notifications 1}
notificationTypesPrefix     OBJECT IDENTIFIER ::= {notificationTypes 0}
notificationFields          OBJECT IDENTIFIER ::= {notifications 2}

metricObjectsGroup OBJECT-GROUP
    OBJECTS { 
            kind,
            title,
            periodSec,         
            lowErrorVal,       
            lowWarnVal,        
            highWarnVal,       
            highErrorVal,      
            warnDelaySec,      
            errorDelaySec,     
            escalationDelaySec, 
            instanceId,   
            unitId,       
            systemId,     
            serviceUri,   
            netChannelId,
            timingSection,
            begTime,      
            endTime,      
            begVal,       
            endVal,       
            minVal,       
            maxVal,       
            avgVal   
    }
    STATUS  current
    DESCRIPTION
            "Objects for accessing RadixWare system monitoring data"
    ::= { snmpObjectGroups 1 }

notificationObjectsGroup OBJECT-GROUP
    OBJECTS { 
            metricTypeId,
            metricStateId,
            oldSeverity,
            newSeverity,
            changeTime,
            valueAsString,
            reason
    }
    STATUS  current
    DESCRIPTION
            "Objects used as required fields in notification message"
    ::= { snmpObjectGroups 2 }



metricNotificationsGroup NOTIFICATION-GROUP 
    NOTIFICATIONS {
            metricSeverityChange
    }
    STATUS  current
    DESCRIPTION
        "Notifications about metric severity level changes"
    ::= { snmpNotificationGroups 1}



radixwareMibCompliance MODULE-COMPLIANCE
    STATUS  current
    DESCRIPTION
            "The compliance statement for RadixWare system"
    MODULE  
       MANDATORY-GROUPS { 
                metricObjectsGroup,
                metricNotificationsGroup,
                notificationObjectsGroup 
            }
::= { mibCompliances 1 }

-- Textual conventions --
   
Positive32TC ::= TEXTUAL-CONVENTION
    DISPLAY-HINT "d"
    STATUS       current
    DESCRIPTION "Positive integer based on SNMP type Integer32."
    SYNTAX Integer32 (0..2147483647)

Decimal2TC ::= TEXTUAL-CONVENTION
    DISPLAY-HINT "d-2"
    STATUS       current
    DESCRIPTION  "Decimal value with 2 points after dot based on Integer32."
    SYNTAX Integer32 (-2147483648..2147483647)

SeverityTC ::= TEXTUAL-CONVENTION
    STATUS       current
    DESCRIPTION  "Severity level encoded as integer"
    SYNTAX       INTEGER {
                     event(1),
                     warning(2),
                     error(3)
                 }

ReasonTC ::= TEXTUAL-CONVENTION
    STATUS       current
    DESCRIPTION  "Reason of severity change encoded as integer"
    SYNTAX       INTEGER {
                     valueChanged(0),
                     escalation(1)
                 }

UTF8String ::= TEXTUAL-CONVENTION
    DISPLAY-HINT "255t"
    STATUS       current
    DESCRIPTION "UTF-8 String"
    SYNTAX       OCTET STRING (SIZE (0..255))

-- Metric objects --

metricTypeTable OBJECT-TYPE
    SYNTAX      SEQUENCE OF MetricTypeTableEntry
    MAX-ACCESS  not-accessible
    STATUS      current
    DESCRIPTION "Table that lists all metric types accessible for SNMP managers"
    ::= { metrics 1 }

-- Metric Type Table --

metricTypeTableEntry OBJECT-TYPE
    SYNTAX      MetricTypeTableEntry
    MAX-ACCESS  not-accessible
    STATUS      current
    DESCRIPTION	"Entry for metricTypeTable"
    INDEX { metricTypeTableIndex }
    ::= { metricTypeTable 1 }

MetricTypeTableEntry ::= SEQUENCE {
    metricTypeTableIndex Positive32TC,
    kind                 DisplayString,
    title                UTF8String,
    periodSec            Positive32TC,
    lowErrorVal          Decimal2TC,
    lowWarnVal           Decimal2TC,
    highWarnVal          Decimal2TC,
    highErrorVal         Decimal2TC,
    warnDelaySec         Positive32TC,   
    errorDelaySec        Positive32TC,
    escalationDelaySec   Positive32TC
}

metricTypeTableIndex OBJECT-TYPE
    SYNTAX      Positive32TC
    MAX-ACCESS  not-accessible
    STATUS      current
    DESCRIPTION "MetricType.ID"
    ::= { metricTypeTableEntry 1 }

kind OBJECT-TYPE
    SYNTAX      DisplayString
    MAX-ACCESS  read-only
    STATUS      current
    DESCRIPTION "Metric kind name"
    ::= { metricTypeTableEntry 2 }

title OBJECT-TYPE
    SYNTAX      UTF8String
    MAX-ACCESS  read-only
    STATUS      current
    DESCRIPTION "Metric title"
    ::= { metricTypeTableEntry 3 }

periodSec OBJECT-TYPE
    SYNTAX      Positive32TC
    MAX-ACCESS  read-only
    STATUS      current
    DESCRIPTION "MetricType.period, -2147483648 for null"
    ::= { metricTypeTableEntry 4 }

lowErrorVal OBJECT-TYPE
    SYNTAX      Decimal2TC
    MAX-ACCESS  read-only
    STATUS      current
    DESCRIPTION "MetricType.lowErrorVal, -2147483648 for null"
    ::= { metricTypeTableEntry 5 }

lowWarnVal OBJECT-TYPE
    SYNTAX      Decimal2TC
    MAX-ACCESS  read-only
    STATUS      current
    DESCRIPTION "MetricType.lowErrorVal, -2147483648 for null"
    ::= { metricTypeTableEntry 6 }

highWarnVal OBJECT-TYPE
    SYNTAX      Decimal2TC
    MAX-ACCESS  read-only
    STATUS      current
    DESCRIPTION "MetricType.highWarnVal, -2147483648 for null"
    ::= { metricTypeTableEntry 7 }

highErrorVal OBJECT-TYPE
    SYNTAX      Decimal2TC
    MAX-ACCESS  read-only
    STATUS      current
    DESCRIPTION "MetricType.highErrorVal, -2147483648 for null"
    ::= { metricTypeTableEntry 8 }

warnDelaySec OBJECT-TYPE
    SYNTAX      Positive32TC
    MAX-ACCESS  read-only
    STATUS      current
    DESCRIPTION "MetricType.warnDelay"
    ::= { metricTypeTableEntry 9 }

errorDelaySec OBJECT-TYPE
    SYNTAX      Positive32TC
    MAX-ACCESS  read-only
    STATUS      current
    DESCRIPTION "MetricType.errorDelay"
    ::= { metricTypeTableEntry 10 }

escalationDelaySec OBJECT-TYPE
    SYNTAX      Positive32TC
    MAX-ACCESS  read-only
    STATUS      current
    DESCRIPTION "MetricType.escalationDelay"
    ::= { metricTypeTableEntry 11 }

-- Metric State Table --

metricStateTable OBJECT-TYPE
    SYNTAX      SEQUENCE OF MetricStateTableEntry
    MAX-ACCESS  not-accessible
    STATUS      current
    DESCRIPTION "Table that lists all metric types accessible for SNMP managers"
    ::= { metrics 2 }

metricStateTableEntry OBJECT-TYPE
    SYNTAX      MetricStateTableEntry
    MAX-ACCESS  not-accessible
    STATUS      current
    DESCRIPTION	"Entry for metricStateTable"
    INDEX { metricTypeTableIndex, metricStateTableIndex }
    ::= { metricStateTable 1 }

MetricStateTableEntry ::= SEQUENCE {
    metricStateTableIndex Positive32TC,
    instanceId            Positive32TC,
    unitId                Positive32TC,
    systemId              Positive32TC,
    serviceUri            DisplayString,
    netChannelId          Positive32TC,
    timingSection         DisplayString,
    begTime               DateAndTime,
    endTime               DateAndTime,
    begVal                Decimal2TC,
    endVal                Decimal2TC,
    minVal                Decimal2TC,
    maxVal                Decimal2TC,
    avgVal                Decimal2TC
}

metricStateTableIndex OBJECT-TYPE
    SYNTAX      Positive32TC
    MAX-ACCESS  not-accessible
    STATUS      current
    DESCRIPTION "MetricState.ID"
    ::= { metricStateTableEntry 1 }

instanceId OBJECT-TYPE
    SYNTAX      Positive32TC
    MAX-ACCESS  read-only
    STATUS      current
    DESCRIPTION "MetricState.instanceId"
    ::= { metricStateTableEntry 2 }

unitId OBJECT-TYPE
    SYNTAX      Positive32TC
    MAX-ACCESS  read-only
    STATUS      current
    DESCRIPTION "MetricState.unitId"
    ::= { metricStateTableEntry 3 }

systemId OBJECT-TYPE
    SYNTAX      Positive32TC
    MAX-ACCESS  read-only
    STATUS      current
    DESCRIPTION "MetricState.systemId"
    ::= { metricStateTableEntry 4 }

serviceUri OBJECT-TYPE
    SYNTAX      DisplayString
    MAX-ACCESS  read-only
    STATUS      current
    DESCRIPTION "MetricState.serviceUri"
    ::= { metricStateTableEntry 5 }

netChannelId OBJECT-TYPE
    SYNTAX      Positive32TC
    MAX-ACCESS  read-only
    STATUS      current
    DESCRIPTION "MetricState.netChannelId"
    ::= { metricStateTableEntry 6 }

timingSection OBJECT-TYPE
    SYNTAX      DisplayString
    MAX-ACCESS  read-only
    STATUS      current
    DESCRIPTION "MetricType.timingSection"
    ::= { metricStateTableEntry 7 }

begTime OBJECT-TYPE
    SYNTAX      DateAndTime
    MAX-ACCESS  read-only
    STATUS      current
    DESCRIPTION "MetricState.begTime"
    ::= { metricStateTableEntry 8 }

endTime OBJECT-TYPE
    SYNTAX      DateAndTime
    MAX-ACCESS  read-only
    STATUS      current
    DESCRIPTION "MetricState.endTime"
    ::= { metricStateTableEntry 9 }

begVal OBJECT-TYPE
    SYNTAX      Decimal2TC
    MAX-ACCESS  read-only
    STATUS      current
    DESCRIPTION "MetricState.begVal, -2147483648 for null"
    ::= { metricStateTableEntry 10 }

endVal OBJECT-TYPE
    SYNTAX      Decimal2TC
    MAX-ACCESS  read-only
    STATUS      current
    DESCRIPTION "MetricState.endVal, -2147483648 for null"
    ::= { metricStateTableEntry 11 }

minVal OBJECT-TYPE
    SYNTAX      Decimal2TC
    MAX-ACCESS  read-only
    STATUS      current
    DESCRIPTION "MetricState.minVal, -2147483648 for null"
    ::= { metricStateTableEntry 12 }

maxVal OBJECT-TYPE
    SYNTAX      Decimal2TC
    MAX-ACCESS  read-only
    STATUS      current
    DESCRIPTION "MetricState.maxVal, -2147483648 for null"
    ::= { metricStateTableEntry 13 }

avgVal OBJECT-TYPE
    SYNTAX      Decimal2TC
    MAX-ACCESS  read-only
    STATUS      current
    DESCRIPTION "MetricState.avgVal, -2147483648 for null"
    ::= { metricStateTableEntry 14}


-- Definitions for notifications --

metricTypeId OBJECT-TYPE
    SYNTAX      Positive32TC
    MAX-ACCESS  read-only
    STATUS      current
    DESCRIPTION "ID of the corresponding metric type object"
    ::= { notificationFields 1 }

metricStateId OBJECT-TYPE
    SYNTAX      Positive32TC
    MAX-ACCESS  read-only
    STATUS      current
    DESCRIPTION "ID of the corresponding metric state object"
    ::= { notificationFields 2 }

oldSeverity OBJECT-TYPE
    SYNTAX      SeverityTC
    MAX-ACCESS  read-only
    STATUS      current
    DESCRIPTION "Old severity level"
    ::= { notificationFields 3 }

newSeverity OBJECT-TYPE
    SYNTAX      SeverityTC
    MAX-ACCESS  read-only
    STATUS      current
    DESCRIPTION "Old severity level"
    ::= { notificationFields 4 }

changeTime OBJECT-TYPE
    SYNTAX      DateAndTime
    MAX-ACCESS  read-only
    STATUS      current
    DESCRIPTION "Severity change time, for event and point metrics - endTime,
                 for statistic metrics - begTime"
    ::= { notificationFields 5 }

valueAsString OBJECT-TYPE
    SYNTAX      DisplayString
    MAX-ACCESS  read-only
    STATUS      current
    DESCRIPTION "Value which caused severity change"
    ::= { notificationFields 6 }

reason OBJECT-TYPE
    SYNTAX      ReasonTC
    MAX-ACCESS  read-only
    STATUS      current
    DESCRIPTION "Reason for severity change"
    ::= { notificationFields 7 }
    

metricSeverityChange NOTIFICATION-TYPE
    OBJECTS {
        metricTypeId,
        metricStateId,
        kind,
        title,
        oldSeverity,
        newSeverity,
        changeTime,
        valueAsString,
        reason
    }
    STATUS             current
    DESCRIPTION
            "An event which is generated when RadixWare based system
             discovers that severity of the certain metric has changed"
    ::= { notificationTypesPrefix 1 }

END
